SDP DEFINITIONS IMPLICIT TAGS ::=
BEGIN

EXPORTS SDPMsg, ParameterType;

SDPMsg ::= SEQUENCE {
        sDPMsgHeader            [0]     SDPMsgHeader,
        sDPMsgBody              [1]     SDPMsgBody
}

SDPMsgHeader ::= SEQUENCE {
        version                 [0]     INTEGER,
        protocolSubsystem       [1]     INTEGER,
        sCPHandle               [2]     INTEGER,
        sDPHandle               [3]     INTEGER,
        msgClass                [4]     INTEGER,
        genericError            [5]     ErrorCode,
        timeStamp               [6]     INTEGER,
        priority                [7]     Priority
}

SDPMsgBody ::= CHOICE {
        sendMsgReq              [0]     SendMsgReq,
        sendMsgResp             [1]     SendMsgResp,
        alarm                   [2]     Alarm,
        sSTReq                  [3]     SSTReq,
        sSTResp                 [4]     SSTResp
}

END
